# controle_documento

## Frenagem: Requisitios relativos ao sistema de freios (Container)

### arquitetura do EBS (Functional)
O veiculo deve possuir um sistema de frenagem de emergencia

### sistema de freio de emergencia (Functional)
o sistema deve ser acionado quando houver um obstaculo detectado pelo box

#### Funcionamento EBS: Em caso de emergencia um EBS_signal baixo oriundo do box deve acionar a EBS_solenoide (Functional)

## Esterçamento (Container)

### Limite de esterçamento: O veiculo deve esterçar no maximo de -36 a 36 graus +/- 0.1 grau (Functional)

## Longitudinal (Functional)

### settling time: o settling time nao deve ser maio que 1.5 segundos (Functional)

### overshoot: o overshoot nao pode ser maior que 2 porcento (Functional)

### percent rise: o percent rise deve ser igual ou maior que 80 porcento (Functional)

### percent settling: o percent settling deve ser igual ou menor que 1 porcento (Functional)

### undershoot: o undershoot deve ser igual ou menor que 3 porcento (Functional)

### rise time: o rise time deve ser igual ou menor que 1 segundo (Functional)
